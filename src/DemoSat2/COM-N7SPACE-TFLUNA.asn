COM-N7SPACE-TFLUNA DEFINITIONS ::= BEGIN
IMPORTS
Word FROM COM-N7SPACE-HWAS
;
-- Enum listing UART read data frame state machine states
TfLuna-ReadSM ::= ENUMERATED
{
    tfLuna-ReadSM-Idle(0),
    tfLuna-ReadSM-Head(1),
    tfLuna-ReadSM-DistanceLow(3),
    tfLuna-ReadSM-DistanceHigh(4),
    tfLuna-ReadSM-StrengthLow(5),
    tfLuna-ReadSM-StrengthHigh(6),
    tfLuna-ReadSM-TemperatureLow(7),
    tfLuna-ReadSM-TemperatureHigh(8),
    tfLuna-ReadSM-Checksum(9)
}
-- Lidar data container (Distance, signal strength and temperature)
TfLuna-Data ::= SEQUENCE 
{ 
    mDistance Word(0 .. 4294967295), 
    mStrength Word(0 .. 4294967295), 
    mTemp Word(0 .. 4294967295)
} 
-- Enum listing possible rx errors
TfLuna-DataFrameErr ::= ENUMERATED
{
    tfLuna-DataFrameErr-NoHead1(0),
    tfLuna-DataFrameErr-NoHead2(1),
    tfLuna-DataFrameErr-WrongCrc(2),
    tfLuna-DataFrameErr-WrongState(3)
}
TfLunaReturnInterfaceType-ReadDataCmd-Type ::= SEQUENCE 
{ 
    lidarTfLunaData TfLuna-Data
} 
TfLunaReturnInterfaceType-ErrorReadDataCmd-Type ::= SEQUENCE 
{ 
    err TfLuna-DataFrameErr
} 
END
