COM-N7SPACE-AFECHWAS DEFINITIONS ::= BEGIN
DestinationAddress ::= INTEGER(0 .. 4294967295)
SourceAddress ::= INTEGER(0 .. 4294967295)
Word ::= INTEGER(0 .. 4294967295)
WordMask ::= INTEGER(0 .. 4294967295)
AfecHwas-Instance ::= ENUMERATED
{
    afecHwas-Instance-Afec0(0),
    afecHwas-Instance-Afec1(1)
}
AfecHwas-StartupTime ::= INTEGER(0 .. 15)
AfecHwasChannel ::= INTEGER(0 .. 15)
AfecHwas ::= SEQUENCE 
{ 
    mInstanceAddress DestinationAddress(0 .. 4294967295), 
    mInstanceMrAddress DestinationAddress(0 .. 4294967295), 
    mInstanceEmrAddress DestinationAddress(0 .. 4294967295), 
    mInstanceChdrAddress DestinationAddress(0 .. 4294967295), 
    mInstanceCherAddress DestinationAddress(0 .. 4294967295), 
    mInstanceChsrAddress DestinationAddress(0 .. 4294967295), 
    mInstanceCrAddress DestinationAddress(0 .. 4294967295), 
    mInstanceIsrAddress DestinationAddress(0 .. 4294967295), 
    mInstanceLcdrAddress DestinationAddress(0 .. 4294967295)
} 
AfecHwasConfig ::= SEQUENCE 
{ 
    mAfecInstance AfecHwas-Instance, 
    mStartupTime AfecHwas-StartupTime(0 .. 15), 
    mPrescalerValue Word(0 .. 4294967295)
} 
PmcHwas ::= SEQUENCE 
{ 
    pMC-PCER0-OFFSET DestinationAddress(0 .. 4294967295), 
    pMC-PCER1-OFFSET DestinationAddress(0 .. 4294967295), 
    pMC-PCxR0-PID29-AFEC0-MASK WordMask(0 .. 4294967295), 
    pMC-PCxR1-PID40-AFEC1-MASK WordMask(0 .. 4294967295)
} 
END
