Manager-Datamodel DEFINITIONS ::=
BEGIN
IMPORTS
   DestinationAddress, SourceAddress, Word, WordMask, AfecHwas-Instance, AfecHwas-StartupTime, AfecHwasChannel, AfecHwas, AfecHwasConfig, PmcHwas FROM COM-N7SPACE-AFECHWAS
   InterruptNumber, Byte, ByteBuffer, Interrupt-Type FROM COM-N7SPACE-HWAS
   MyInteger FROM SAMV71AFEC-DATAVIEW
   T-Int32, T-UInt32, T-Int8, T-UInt8, T-Boolean, T-Null-Record FROM TASTE-BasicTypes;

Manager-States ::= ENUMERATED {wait}

Manager-Context ::= SEQUENCE {
   state Manager-States,
   init-done BOOLEAN
}

END
