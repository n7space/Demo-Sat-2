COM-N7SPACE-AFECHWAS DEFINITIONS ::= BEGIN
DestinationAddress ::= INTEGER(0 .. 4294967295)
SourceAddress ::= INTEGER(0 .. 4294967295)
Word ::= INTEGER(0 .. 4294967295)
WordMask ::= INTEGER(0 .. 4294967295)
AfecHwas-Instance ::= ENUMERATED
{
    afecHwas-Instance-Afec0(0),
    afecHwas-Instance-Afec1(1)
}
AfecHwas-StartupTime ::= INTEGER(0 .. 15)
AfecHwasChannel ::= INTEGER(0 .. 15)
AfecHwas ::= SEQUENCE 
{ 
    mInstanceAddress DestinationAddress(0 .. 4294967295), 
    mInstanceMrAddress DestinationAddress(0 .. 4294967295), 
    mInstanceEmrAddress DestinationAddress(0 .. 4294967295), 
    mInstanceChdrAddress DestinationAddress(0 .. 4294967295), 
    mInstanceCherAddress DestinationAddress(0 .. 4294967295), 
    mInstanceChsrAddress DestinationAddress(0 .. 4294967295), 
    mInstanceCrAddress DestinationAddress(0 .. 4294967295), 
    mInstanceIsrAddress DestinationAddress(0 .. 4294967295), 
    mInstanceLcdrAddress DestinationAddress(0 .. 4294967295)
} 
AfecHwasConfig ::= SEQUENCE 
{ 
    mAfecInstance AfecHwas-Instance, 
    mStartupTime AfecHwas-StartupTime(0 .. 15), 
    mPrescalerValue Word(0 .. 4294967295)
} 
PmcHwas ::= SEQUENCE 
{ 
    pMC-PCER0-OFFSET DestinationAddress(0 .. 4294967295), 
    pMC-PCER1-OFFSET DestinationAddress(0 .. 4294967295), 
    pMC-PCxR0-PID29-AFEC0-MASK WordMask(0 .. 4294967295), 
    pMC-PCxR1-PID40-AFEC1-MASK WordMask(0 .. 4294967295)
} 
END


COM-N7SPACE-HWAS DEFINITIONS ::= BEGIN
InterruptNumber ::= INTEGER(0 .. 255)
Byte ::= INTEGER(0 .. 255)
ByteBuffer ::= SEQUENCE (SIZE(0 .. 65535)) OF Byte(0 .. 255)
Interrupt-Type ::= SEQUENCE 
{ 
    interrupt InterruptNumber(0 .. 255)
} 
END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END
