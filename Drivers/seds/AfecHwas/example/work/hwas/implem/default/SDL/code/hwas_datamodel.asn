Hwas-Datamodel DEFINITIONS ::=
BEGIN
IMPORTS
   DestinationAddress, SourceAddress, Word, WordMask, AfecHwas-Instance, AfecHwas-StartupTime, AfecHwasChannel, AfecHwas, AfecHwasConfig, PmcHwas FROM COM-N7SPACE-AFECHWAS
   InterruptNumber, Byte, ByteBuffer, Interrupt-Type FROM COM-N7SPACE-HWAS
   MyInteger FROM SAMV71AFEC-DATAVIEW
   T-Int32, T-UInt32, T-Int8, T-UInt8, T-Boolean, T-Null-Record FROM TASTE-BasicTypes;

Hwas-States ::= ENUMERATED {wait}

Hwas-Context ::= SEQUENCE {
   state Hwas-States,
   init-done BOOLEAN
}

END
