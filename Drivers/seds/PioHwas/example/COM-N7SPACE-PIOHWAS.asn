COM-N7SPACE-PIOHWAS DEFINITIONS ::= BEGIN
IMPORTS
DestinationAddress FROM COM-N7SPACE-HWAS
Word FROM COM-N7SPACE-HWAS
WordMask FROM COM-N7SPACE-HWAS
;
PinNumber ::= INTEGER(0 .. 15)
-- Definitions of PIO ports
PioHwas-Port ::= ENUMERATED
{
    pioHwas-Port-A(0),
    pioHwas-Port-B(1),
    pioHwas-Port-C(2),
    pioHwas-Port-D(3),
    pioHwas-Port-E(4)
}
-- I/O line flow direction
PioHwas-Direction ::= ENUMERATED
{
    pioHwas-Direction-Input(0),
    pioHwas-Direction-Output(1)
}
-- Pio descriptor
PioHwas ::= SEQUENCE 
{ 
    mPortAddress DestinationAddress(0 .. 4294967295), 
    mPin Word(0 .. 4294967295), 
    mPortPerAddress DestinationAddress(0 .. 4294967295), 
    mPortOerAddress DestinationAddress(0 .. 4294967295), 
    mPortOdrAddress DestinationAddress(0 .. 4294967295), 
    mPortIfdrAddress DestinationAddress(0 .. 4294967295), 
    mPortSodrAddress DestinationAddress(0 .. 4294967295), 
    mPortCodrAddress DestinationAddress(0 .. 4294967295), 
    mPortOdsrAddress DestinationAddress(0 .. 4294967295), 
    mPortMddrAddress DestinationAddress(0 .. 4294967295), 
    mPortPudrAddress DestinationAddress(0 .. 4294967295), 
    mPortOwerAddress DestinationAddress(0 .. 4294967295), 
    mPortOwdrAddress DestinationAddress(0 .. 4294967295), 
    mPortIfscdrAddress DestinationAddress(0 .. 4294967295), 
    mPortPpddrAddress DestinationAddress(0 .. 4294967295), 
    mPortSchmittAddress DestinationAddress(0 .. 4294967295)
} 
-- Pin configuration container
PioHwasPinConfig ::= SEQUENCE 
{ 
    mPortConfig PioHwas-Port, 
    mPinConfig PinNumber(0 .. 15), 
    mDirectionConfig PioHwas-Direction
} 
-- Pmc descriptor
PmcHwas ::= SEQUENCE 
{ 
    pMC-PCER0-OFFSET DestinationAddress(0 .. 4294967295), 
    pMC-PCxR0-PID10-PIOA-MASK WordMask(0 .. 4294967295), 
    pMC-PCxR0-PID11-PIOB-MASK WordMask(0 .. 4294967295), 
    pMC-PCxR0-PID12-PIOC-MASK WordMask(0 .. 4294967295), 
    pMC-PCxR0-PID16-PIOD-MASK WordMask(0 .. 4294967295), 
    pMC-PCxR0-PID17-PIOE-MASK WordMask(0 .. 4294967295)
} 
END
