COM-N7SPACE-HWAS DEFINITIONS ::= BEGIN
DestinationAddress ::= INTEGER(0 .. 4294967295)
SourceAddress ::= INTEGER(0 .. 4294967295)
Word ::= INTEGER(0 .. 4294967295)
WordMask ::= INTEGER(0 .. 4294967295)
BufferSize ::= INTEGER(0 .. 32000)
InterruptNumber ::= INTEGER(0 .. 255)
Byte ::= INTEGER(0 .. 255)
ByteBuffer ::= SEQUENCE (SIZE(0 .. 32000)) OF Byte(0 .. 255)
Interrupt-Type ::= SEQUENCE 
{ 
    interrupt InterruptNumber(0 .. 255)
} 
END


COM-N7SPACE-PIOHWAS DEFINITIONS ::= BEGIN
DestinationAddress ::= INTEGER(0 .. 4294967295)
SourceAddress ::= INTEGER(0 .. 4294967295)
Word ::= INTEGER(0 .. 4294967295)
WordMask ::= INTEGER(0 .. 4294967295)
BufferSize ::= INTEGER(0 .. 32000)
InterruptNumber ::= INTEGER(0 .. 255)
Byte ::= INTEGER(0 .. 255)
ByteBuffer ::= SEQUENCE (SIZE(0 .. 32000)) OF Byte(0 .. 255)
PinNumber ::= INTEGER(0 .. 64)
PioHwas-Port ::= ENUMERATED
{
    pioHwas-Port-A(0),
    pioHwas-Port-B(1),
    pioHwas-Port-C(2),
    pioHwas-Port-D(3),
    pioHwas-Port-E(4)
}
PioHwas-Direction ::= ENUMERATED
{
    pioHwas-Direction-Input(0),
    pioHwas-Direction-Output(1)
}
PioHwas ::= SEQUENCE 
{ 
    mPortAddress DestinationAddress(0 .. 4294967295), 
    mPin WordMask(0 .. 4294967295), 
    mPortPerAddress DestinationAddress(0 .. 4294967295), 
    mPortOerAddress DestinationAddress(0 .. 4294967295), 
    mPortOdrAddress DestinationAddress(0 .. 4294967295), 
    mPortIfdrAddress DestinationAddress(0 .. 4294967295), 
    mPortSodrAddress DestinationAddress(0 .. 4294967295), 
    mPortCodrAddress DestinationAddress(0 .. 4294967295), 
    mPortMddrAddress DestinationAddress(0 .. 4294967295), 
    mPortPudrAddress DestinationAddress(0 .. 4294967295), 
    mPortOwerAddress DestinationAddress(0 .. 4294967295), 
    mPortOwdrAddress DestinationAddress(0 .. 4294967295), 
    mPortIfscdrAddress DestinationAddress(0 .. 4294967295), 
    mPortPpddrAddress DestinationAddress(0 .. 4294967295), 
    mPortSchmittAddress DestinationAddress(0 .. 4294967295)
} 
PioHwasPinConfig ::= SEQUENCE 
{ 
    mPortConfig PioHwas-Port, 
    mPinConfig WordMask(0 .. 4294967295), 
    mDirectionConfig PioHwas-Direction
} 
PmcHwas ::= SEQUENCE 
{ 
    pMC-PCSR0-OFFSET DestinationAddress(0 .. 4294967295), 
    pMC-PCxR0-PID10-PIOA-MASK WordMask(0 .. 4294967295), 
    pMC-PCxR0-PID11-PIOB-MASK WordMask(0 .. 4294967295), 
    pMC-PCxR0-PID12-PIOC-MASK WordMask(0 .. 4294967295), 
    pMC-PCxR0-PID16-PIOD-MASK WordMask(0 .. 4294967295), 
    pMC-PCxR0-PID17-PIOE-MASK WordMask(0 .. 4294967295)
} 
END


TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

T-Null-Record ::= SEQUENCE {}

END


TEST3-DATAVIEW DEFINITIONS ::=
BEGIN

   MyInteger ::= INTEGER (0 .. 10000)

-- ASN.1 Type definitions must start with an uppercase
-- Field names in records (SEQUENCE) must start with a lowercase
-- Underscores are not allowed: use dash (hyphen) 
-- For integers do not assume that small ranges will be translated to small
-- types in C or Ada (expect unsigned or signed 64 bits types with subtypes
-- for the range in Ada)

-- Simple types:

-- TASTE-Boolean ::= BOOLEAN
-- MyInteger   ::= INTEGER (0..255)
-- MyReal      ::= REAL (0.0 .. 1000.0)
-- MyBool      ::= BOOLEAN
-- MyEnum      ::= ENUMERATED { hello, world, how-are-you }

-- Complex types:

--  MySeq       ::= SEQUENCE {
--      input-data  MyInteger,
--      output-data MyInteger,
--      validity    ENUMERATED { valid, invalid }
--  }
--
--  MyChoice    ::= CHOICE {
--      a BOOLEAN,
--      b MySeq
--  }
--
--  MySeqOf     ::= SEQUENCE (SIZE (2)) OF MyEnum
--
--  MyOctStr    ::= OCTET STRING (SIZE (3))
--
--  -- You can also declare constants
--  myVar       MySeqOf     ::= { hello, world }

END
