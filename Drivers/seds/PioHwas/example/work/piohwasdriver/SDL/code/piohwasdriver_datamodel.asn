Piohwasdriver-Datamodel DEFINITIONS ::=
BEGIN
IMPORTS
   InterruptNumber, Interrupt-Type FROM COM-N7SPACE-HWAS
   DestinationAddress, SourceAddress, Word, WordMask, BufferSize, Byte, ByteBuffer, PinNumber, PioHwas-Port, PioHwas-Direction, PioHwas, PioHwasPinConfig, PmcHwas FROM COM-N7SPACE-PIOHWAS
   T-Int32, T-UInt32, T-Int8, T-UInt8, T-Boolean, T-Null-Record FROM TASTE-BasicTypes;

Piohwasdriver-States ::= ENUMERATED {idle, off}

Piohwasdriver-Context ::= SEQUENCE {
   state Piohwasdriver-States,
   init-done BOOLEAN,
   piovar PioHwas,
   configvar PioHwasPinConfig,
   pmcvar PmcHwas,
   pinvaluevar Word,
   pinmaskvar WordMask,
   destinationaddressvar DestinationAddress,
   sourceaddressvar SourceAddress
}

END
