COM-N7SPACE-AFECHWAS DEFINITIONS ::= BEGIN
IMPORTS
DestinationAddress FROM COM-N7SPACE-HWAS
Word FROM COM-N7SPACE-HWAS
WordMask FROM COM-N7SPACE-HWAS
;
-- Definitions of PIO ports
AfecHwas-Instance ::= ENUMERATED
{
    afecHwas-Instance-Afec0(0),
    afecHwas-Instance-Afec1(1)
}
-- Value expressing possible Startup Times (0-15) refer to documentation
AfecHwas-StartupTime ::= INTEGER(0 .. 15)
-- Number of AFEC channel (0-11, each AFEC instance has 12 channels)
AfecHwasChannel ::= INTEGER(0 .. 11)
-- Afec descriptor
AfecHwas ::= SEQUENCE 
{ 
    mInstanceAddress DestinationAddress(0 .. 4294967295), 
    mInstanceMrAddress DestinationAddress(0 .. 4294967295), 
    mInstanceEmrAddress DestinationAddress(0 .. 4294967295), 
    mInstanceChdrAddress DestinationAddress(0 .. 4294967295), 
    mInstanceCherAddress DestinationAddress(0 .. 4294967295), 
    mInstanceChsrAddress DestinationAddress(0 .. 4294967295), 
    mInstanceCrAddress DestinationAddress(0 .. 4294967295), 
    mInstanceIsrAddress DestinationAddress(0 .. 4294967295), 
    mInstanceLcdrAddress DestinationAddress(0 .. 4294967295)
} 
-- Afec instance configuration container
AfecHwasConfig ::= SEQUENCE 
{ 
    mAfecInstance AfecHwas-Instance, 
    mStartupTime AfecHwas-StartupTime(0 .. 15), 
    mPrescalerValue Word(0 .. 4294967295)
} 
-- Pmc descriptor
PmcAfecHwas ::= SEQUENCE 
{ 
    pMC-PCER0-OFFSET DestinationAddress(0 .. 4294967295), 
    pMC-PCER1-OFFSET DestinationAddress(0 .. 4294967295), 
    pMC-PCxR0-PID29-AFEC0-MASK WordMask(0 .. 4294967295), 
    pMC-PCxR1-PID40-AFEC1-MASK WordMask(0 .. 4294967295)
} 
END
