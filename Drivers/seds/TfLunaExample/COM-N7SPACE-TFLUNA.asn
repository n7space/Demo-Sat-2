COM-N7SPACE-TFLUNAHWAS DEFINITIONS ::= BEGIN
IMPORTS
Word FROM COM-N7SPACE-HWAS
;
-- Enum listing UART read data frame state machine states
TfLunaHwas-ReadSM ::= ENUMERATED
{
    tfLunaHwas-ReadSM-NotFound(0),
    tfLunaHwas-ReadSM-Head(1),
    tfLunaHwas-ReadSM-DisL(3),
    tfLunaHwas-ReadSM-DisH(4),
    tfLunaHwas-ReadSM-StrengthL(5),
    tfLunaHwas-ReadSM-StrengthH(6),
    tfLunaHwas-ReadSM-TempL(7),
    tfLunaHwas-ReadSM-TempH(8),
    tfLunaHwas-ReadSM-Checksum(9)
}
-- Lidar data container (Distance, signal strength and temperature)
TfLunaHwas-Data ::= SEQUENCE 
{ 
    mDistance Word(0 .. 4294967295), 
    mStrength Word(0 .. 4294967295), 
    mTemp Word(0 .. 4294967295)
} 
-- Enum listing possible rx errors
TfLunaHwas-DataFrameErr ::= ENUMERATED
{
    tfLunaHwas-DataFrameErr-NoHead1(0),
    tfLunaHwas-DataFrameErr-NoHead2(1),
    tfLunaHwas-DataFrameErr-WrongCrc(2),
    tfLunaHwas-DataFrameErr-WrongState(3)
}
END
